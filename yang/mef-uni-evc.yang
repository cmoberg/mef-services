module mef-uni-evc {
  namespace "http://tail-f.com/mef-uni-evc";    
  prefix mef-uni-evc;

  import mef-itu-types {
    prefix mef-itu-t;
  }

  import mef-cos {
    prefix mef-cos;
  }

  typedef vlan-id {
    type int32 {
      range "1..4094";
    }
    description 
      "The VLAN-ID that uniquely identifies a VLAN.  This is the
       12-bit  VLAN-ID used in the VLAN Tag header. The range is
       defined by the REFERENCED specification.";
    reference 
      "IEEE Std 802.1Q 2003 Edition, Virtual Bridged Local
       Area Networks.";
  }

  typedef ieee-8021-priority {
    type uint8 {
      range "0..7";
    }
    description "An 802.1Q user priority value.";
    reference "IEEE 802.1Q";
  }

  typedef service-frame-delivery-type {
    type enumeration {
      enum discard;
      enum unconditional;
      enum conditional;
    }
    description 
      "A MEF service frame can have one of three different delivery
       types:
       - Discard: Service Frames are discarded
       - Unconditional: Service Frames are unconditionally delivered
         no matter the content of the Service Frame. An example of
         this is a Point-to-Point EVC.
       - Conditional: Service Frame are conditionally delivered to the
         destination UNI. The condition is specified, for example via
         a bandwidth profile or unicast MAC address learning.";
    reference
      "MEF 10.3 Ethernet Service Attributes Phase 3, October 2013";
  }

  feature ietf-interface-model {
    description
      "This feature indicates that the device implements the
       ietf-interfaces module";

    reference
      "IETF RFC 7223 - A YANG Data Model for Interface Management";
  }

  container mef-service-interfaces {

    list interface {
      key index;

      leaf index {
        type uint32;
      }

      leaf type {
        type bits {
          bit uni-type-1-dot-1;
          bit uni-type-1-dot-2;
          bit uni-type-2-dot-1;
          bit uni-type-2-dot-2;
          bit enni;
          bit vuni-on-enni;
        }
        default uni-type-1-dot-1;
      }

      leaf identifier {
        type string;
        default "";
      }

      leaf ietf-interface-identifier {
        if-feature ietf-interface-model;
        type string;
        description
          "The name value of a corrsponding entry in the
           /interfaces/interface list in the IETF interface model";
      }

      leaf frame-format {
        type enumeration {
          enum no-tag;
          enum c-tag;
          enum s-tag;
          enum s-tag-c-tag;
        }
        default no-tag;
      }

      leaf-list ingress-bwp-group {
        type leafref {
          path "/mef-cos:performance-profile/mef-cos:id";
        }
      }

      leaf-list engress-bwp-group {
        type leafref {
          path "/mef-cos:performance-profile/mef-cos:id";
        }
      }

      leaf-list l2cp-group {
        type leafref {
          path "/mef-cos:performance-profile/mef-cos:id";
        }
      }
    }
  }

  container mef-service-uni {

    list uni {
      key index;

      leaf index {
        type uint32;
      }

      leaf identifier {
        type string;
        default "#";
      }

      leaf bundling-multiplex {
        type enumeration {
          enum all-to-one;
          enum bundling;
          enum multiplex;
          enum bundling-multiplex;
        }
        default all-to-one;
      }

      leaf ce-vlan-id-untagged {
        type vlan-id;
        default 1;
      }

      leaf ce-vlan-id-priority-untagged {
        type ieee-8021-priority;
        default 0;
      }
    }

    list evc-per-uni {
      key index;

      leaf index {
        type uint32;
      }

      leaf service-type {
        type enumeration {
          enum epl;
          enum evpl;
          enum eplan;
          enum evplan;
          enum eptree;
          enum evptree;
        }
        default epl;
        config false;
      }

      leaf identifier {
        type string {
          length "0..90";
        }
        config false;
      }

      leaf ce-vlan-map {
        type string {
          length "0..255";
        }
        default 1:4095;
      }

      leaf-list ingress-bwp-group {
        type leafref {
          path "/mef-cos:performance-profile/mef-cos:id";
        }
      }

      leaf-list engress-bwp-group {
        type leafref {
          path "/mef-cos:performance-profile/mef-cos:id";
        }
      }        
    }
  }

  container mef-service-evc {

    list evc {
      key identifier;
  
      leaf identifier {
	type string{
          length "0..45";
        }
	description
	  "";
      }

      leaf service-type {
	type enumeration {
	  enum point-to-point;
	  enum multipoint-to-multipoint;
          enum rooted-multipoint;

	}
        default point-to-point;
	description
          "";
      }

      leaf max-service-frame-size {
        type uint32 {
          range "1522..16384";
        }
      }

      leaf ce-vlan-id-preservation {
	type enumeration {
          enum preserve;
          enum no-preserve;
        }
	description
	  "";
      }

      leaf ce-vlan-cos-preservation {
	type enumeration{
          enum preserve;
          enum no-preserve;
        }
	description
	  "";
      }

      leaf unicast-delivery {
        type service-frame-delivery-type;
        default unconditional;
      }

      leaf multicast-delivery {
        type service-frame-delivery-type;
        default unconditional;
      }

      leaf broadcast-delivery {
        type service-frame-delivery-type;
        default unconditional;
      }

      leaf-list ingress-bwp-group {
	type leafref {
	  path "/mef-cos:performance-profile/mef-cos:id";
	}
      }

      leaf-list egress-bwp-group {
        type leafref {
          path "/mef-cos:performance-profile/mef-cos:id";
        }
      }
      leaf-list l2cp-group {
        type leafref {
          path "/mef-cos:performance-profile/mef-cos:id";
        }
      }

      // MUST max 1 if point-to-point

      leaf admin-state {
	type mef-itu-t:admin-state-t;
        default unlocked;
	description
	  "";
      }
    }

    list evc-uni {
      key "evc-identifier index";
      leaf evc-identifier {
        type string;
      }

      leaf index {
        type uint32;
      }

      leaf type {
        type enumeration {
          enum root;
          enum leaf;
          enum unknown;
        }
        default root;
      }
    }
  }
}
