module mef-evc-service {
  namespace "http://com/example/mefevcservice";    
  prefix mef-evc-service;

  import mef-profiles {
    prefix mef-profiles;
  }
    import tailf-ncs {
        prefix ncs;
    }
    description "This module models a MEF EVC service based on MEF 10.3.";


  typedef vlan-id {
    type int32 {
      range "1..4094";
    }
    description 
      "The VLAN-ID that uniquely identifies a VLAN.  This is the
       12-bit  VLAN-ID used in the VLAN Tag header. The range is
       defined by the REFERENCED specification.";
    reference 
      "IEEE Std 802.1Q 2003 Edition, Virtual Bridged Local
       Area Networks.";
  }

  typedef ieee-8021-priority {
    type uint8 {
      range "0..7";
    }
    description "An 802.1Q user priority value.";
    reference "IEEE 802.1Q";
  }

  typedef service-frame-delivery-type {
    type enumeration {
      enum discard;
      enum unconditional;
      enum conditional;
    }
    description 
      "A MEF service frame can have one of three different delivery
       types:
       - Discard: Service Frames are discarded
       - Unconditional: Service Frames are unconditionally delivered
         no matter the content of the Service Frame. An example of
         this is a Point-to-Point EVC.
       - Conditional: Service Frame are conditionally delivered to the
         destination UNI. The condition is specified, for example via
         a bandwidth profile or unicast MAC address learning.";
    reference
      "MEF 10.3 Ethernet Service Attributes Phase 3, October 2013";
  }
    typedef entity-admin-state-type {
        type enumeration {
            enum unknown;
            enum locked;
            enum shutting-down;
            enum unlocked;
        }
        description 
         "Represents the various possible administrative states.
          A value of 'locked' means the resource is administratively prohibited from use.  A value of 'shuttingDown' means that usage is administratively limited to current instances of use.  A value of 'unlocked' means the resource is not administratively prohibited from use.  A value of 'unknown' means that this resource is unable to report administrative state.";
        reference "ENTITY-STATE-TC-MIB";
    }
augment /ncs:services {
  container mef-service-evc {

    list eth-fdfr-evc {
      key identifier;
      uses ncs:service-data;
      ncs:servicepoint "mef-evc-service";
      leaf identifier {
	type string{
          length "0..45";
        }
	description
	  "This attribute identifies the name of an ETH_FDFr_EVC instance.";
      }
            leaf label {
                type string;
                description "This attribute represents a friendly name for the ETH_FDFr_EVC instance.";

            }
            leaf user-label {
                type string;
                description "This attribute identifies a text string that may be used to provide additional information about the ETH_FDFr_EVC, such as a circuit identifier.";

            }


      leaf type {
	type enumeration {
	  enum point-to-point;
	  enum multipoint-to-multipoint;
          enum rooted-multipoint;

	}
        default point-to-point;
	description
          "This attribute describes the ETH FDFr_EVC as either Connection_MultipointToMultipoint, Connection_PointToPoint,
           Connection_RootedMultipoint.";
      }

      leaf max-service-frame-size {
        type uint32 {
          range "1522..16384";
        }
                units bytes;
                description "This attribute describes the maximum service frame size for the ETH_FDFr_EVC.";

      }

      leaf ce-vlan-id-preservation {
	type enumeration {
          enum preserve;
          enum no-preserve;
        }
	description
	  "This attribute identifies an EVC where the CE VLAN IDs of egress frames are always identical to the CE VLAN IDs of the corresponding ingress frames.  An EVC with more than one CE-VLAN ID mapping to it MUST have the CE-VLAN ID Preservation Service Attribute and the list of CE-VLAN IDs mapped to the EVC MUST be the same at each UNI in the EVC.";
      }

      leaf ce-vlan-cos-preservation {
	type enumeration{
          enum preserve;
          enum no-preserve;
        }
	description
	  "This attribute identifies an EVC where the CE VLAN CoS user_priority bits of an egress frame is always identical to the CE VLAN CoS user_priority bits of the corresponding ingress frame.";
      }

      leaf unicast-delivery {
        type service-frame-delivery-type;
        default unconditional;
                description "This attribute describes the service frame delivery option for Unicast Service Frames as:  discard, unconditional, or conditional. In the Type definition, the String is to describe the condition for conditional.";

      }

      leaf multicast-delivery {
        type service-frame-delivery-type;
        default unconditional;
                description "This attribute describes the service frame delivery option for multicast Service Frames as:  discard, unconditional, or conditional. In the Type definition, the String is to describe the condition for conditional.";

      }

      leaf broadcast-delivery {
        type service-frame-delivery-type;
        default unconditional;
                description "This attribute describes the service frame delivery option for broadcast Service Frames as:  discard, unconditional, or conditional. In the Type definition, the String is to describe the condition for conditional.";

      }

      // MUST max 1 if point-to-point

      leaf admin-state {
	type entity-admin-state-type;
        default unlocked;
	description
	  "This attribute denotes the administrative state of the ETH_FDFr_EVC. In the locked state frame flow through the ETH_FDFr_EVC is prohibited. ";
      }
            leaf max-uni-end-points {
                type uint32;
                description "This attribute represents the maximum number of UNI end points of the ETH_FDFr_EVC.  For EVC Type of Point-to-Point, this attribute will always be 2.";

            }
            leaf protected {
                type boolean;
                description "This attribute indicates whether the ETH_FDFr_EVC is protected at the ETH layer.";

            }


      leaf-list ingress-bwp-group {
	type leafref {
                    path "/mef-profiles:bandwidth-profile/mef-profiles:identifier";

	}
                description "This attribute identifies the ingress badwidth profile of an ETH_FDFr_EVC instance.";

      }

      leaf-list egress-bwp-group {
        type leafref {
                    path "/mef-profiles:bandwidth-profile/mef-profiles:identifier";

        }
                description "This attribute identifies the egress badwidth profile of an ETH_FDFr_EVC instance.";

      }
            leaf-list performance-group {
                type leafref {
                    path "/mef-profiles:performance-profile/mef-profiles:identifier";
                }
                description "This attribute identifies the performance profile of an ETH_FDFr_EVC instance.";

            }

      leaf-list l2cp-group {
        type leafref {
                    path "/mef-profiles:l2cp-profile/mef-profiles:identifier";

        }
                description "This attribute identifies the Layer 2 Control Protocol profile of an ETH_FDFr_EVC instance.";
                reference "MEF 6.1.1";

      }

    list eth-flow-point {
      key "device interface";
                description "A list of ETH Flow Points. A Flow Point represents the termination of ETH_FDFr_EVC on an ETH_Flow_Domain.  An instance of a ETH_FDFr_EVC may be used to relate two instances of the ETH_Flow_Point.";

                leaf device {
                    type leafref {
                        path "/ncs:devices/ncs:device/ncs:name";
                    }
                }

      leaf interface {
        type string;
        status current;
                    description "This attribute identifies the name of an ETH_Flow_Point instance. The interface identifier on the device referenced by the 'device' leaf above";

      }

      leaf type {
        type enumeration {
          enum root;
          enum leaf;
          enum unknown;
        }
        default root;
        status current;
                    description "This attribute indicates whether the flow point is acting as a root or leaf, and takes on the value either \"root\", \"leaf\" or \"unkown\". If the type of EVC is Point-to-Point or Multipoint-to-Multipoint, then the UNI Type is equal to \"root\". If the type of EVC is Rooted-Multipoint, then the UNI type can be either root or leaf.";

      }
    }
    }
  }
  }
}
